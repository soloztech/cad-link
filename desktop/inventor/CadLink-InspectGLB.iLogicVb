' SPDX-License-Identifier: LGPL-3.0-or-later
' Manual inspection only. Do not attach this rule to a save event.
Sub Main()
    Dim arguments As Inventor.NameValueMap = ThisApplication.TransientObjects.CreateNameValueMap()
    arguments.Add("Inspect", True)
    iLogicVb.RunExternalRule("CadLink-ExportGLB", arguments)
End Sub
